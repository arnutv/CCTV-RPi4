# -*- coding: utf-8 -*-
# ═══════════════════════════════════════════════════════════════════════════
#  CCTV-Camera Enclosure  —  FreeCAD Python Macro
# ═══════════════════════════════════════════════════════════════════════════
#  Generates 2 parts inside the active FreeCAD document, ready for STEP/STL export:
#       1. Electronics tray  (battery + MPPT + boost + BMS inside IP65 box)
#       2. Solar bracket     (L-arm that screws to wall, panel bolts to far end)
#
#  HOW TO USE
#  ──────────
#   1. Open FreeCAD
#   2. Menu:  Macro  →  Macros…  →  "Create"  →  name it "cctv_enclosure"
#   3. Paste the entire contents of this file into the editor
#   4. Click "Execute"  (or F6)
#   5. Two Solids appear in the tree, spread out in the 3-D view
#   6. Right-click each one  →  Export…  →  choose STEP (.step) or Mesh (STL)
#
#  PARAMETRIC EDITS
#  ────────────────
#  Change any value in the PARAMETERS block below, then re-run the macro.
#
#  TESTED ON
#  ─────────
#  FreeCAD 0.21, 0.22, 1.0   (no external workbenches required)
# ═══════════════════════════════════════════════════════════════════════════

import FreeCAD as App
import FreeCADGui as Gui
import Part
from FreeCAD import Vector

# ─── PARAMETERS ───────────────────────────────────────────────────────────
# IP65 box INNER usable dimensions
BOX_W = 134.0   # inner length (140 mm outer − 2×3 mm walls)
BOX_D =  72.0   # inner depth  ( 78 mm outer − 2×3 mm walls)

# Electronics — real measured sizes (mm)
HOLDER_W, HOLDER_D = 75.0, 36.0   # 2× 18650 battery holder
CN3791_W, CN3791_D = 30.0, 20.0   # MPPT charger PCB
MT3608_W, MT3608_D = 36.0, 17.0   # boost converter PCB
BMS_W,    BMS_D    = 20.0, 10.0   # 1S BMS module (DW01A+FS8205A, 20×10 mm)

COL_X = 4 + HOLDER_W + 6          # X of right clip column = 85 mm

# Solar bracket
ARM_L   = 80.0    # horizontal arm length
ARM_W   = 25.0    # arm + plate width
ARM_TH  =  4.0    # arm + plate thickness
PLATE_H = 100.0   # vertical plate height

# Print tolerances
WALL = 1.6
SLOP = 0.3

# ═══════════════════════════════════════════════════════════════════════════
#  PART BUILDERS
# ═══════════════════════════════════════════════════════════════════════════

def make_pcb_clip(pcb_w, pcb_d, h):
    """Two-finger clip that grips a small PCB by its short edges."""
    outer  = Part.makeBox(pcb_w + WALL*2 + SLOP*2,
                          pcb_d + WALL*2 + SLOP*2, h)
    inner  = Part.makeBox(pcb_w + SLOP*2, pcb_d + SLOP*2, h - 1.5)
    inner.translate(Vector(WALL, WALL, 1.6))
    window = Part.makeBox(12, pcb_d + WALL*4 + SLOP*2 + 2, h)
    window.translate(Vector((pcb_w + WALL*2)/2 - 6, -1, 3))
    return outer.cut(inner).cut(window)


def electronics_tray():
    """Floor tray that holds battery + MPPT + boost in fixed positions."""
    tray = Part.makeBox(BOX_W - 4, BOX_D - 4, 2)

    # Battery holder pocket
    pocket_outer = Part.makeBox(HOLDER_W + SLOP*2, HOLDER_D + SLOP*2, 10)
    pocket_outer.translate(Vector(4, 4, 2))
    pocket_inner = Part.makeBox(HOLDER_W + SLOP*2 - WALL*2,
                                HOLDER_D + SLOP*2 - WALL*2, 10)
    pocket_inner.translate(Vector(4 + WALL, 4 + WALL, 4))
    tray = tray.fuse(pocket_outer.cut(pocket_inner))

    # MPPT clip (right column, top)
    mppt = make_pcb_clip(CN3791_W, CN3791_D, 8)
    mppt.translate(Vector(COL_X, 4, 2))
    tray = tray.fuse(mppt)

    # Boost converter clip (right column, middle)
    boost = make_pcb_clip(MT3608_W, MT3608_D, 8)
    boost.translate(Vector(COL_X, 4 + CN3791_D + 5, 2))
    tray = tray.fuse(boost)

    # BMS clip (right column, bottom — under boost)
    bms = make_pcb_clip(BMS_W, BMS_D, 8)
    bms.translate(Vector(COL_X, 4 + CN3791_D + 5 + MT3608_D + 5, 2))
    tray = tray.fuse(bms)

    # Cable routing posts
    for x in (10, BOX_W - 14):
        for y in (10, BOX_D - 14):
            post = Part.makeCylinder(2.0, 12)
            post.translate(Vector(x, y, 2))
            tray = tray.fuse(post)

    # M3 mounting holes
    for x in (6, BOX_W - 10):
        for y in (6, BOX_D - 10):
            hole = Part.makeCylinder(1.7, 5)
            hole.translate(Vector(x, y, -1))
            tray = tray.cut(hole)

    return tray


def solar_bracket():
    """L-shaped wall arm. Vertical plate screws to wall; panel bolts to arm end."""
    # Vertical wall plate with 2× M5 countersunk wall holes
    plate = Part.makeBox(ARM_W, ARM_TH, PLATE_H)
    for z in (15, PLATE_H - 15):
        # M5 clearance hole (⌀5.5) through plate depth
        h = Part.makeCylinder(2.75, ARM_TH + 2,
                              Vector(ARM_W/2, -1, z), Vector(0, 1, 0))
        plate = plate.cut(h)
        # 90° countersink on the back face
        cs = Part.makeCone(5.25, 2.75, 3.2,
                           Vector(ARM_W/2, -0.1, z), Vector(0, 1, 0))
        plate = plate.cut(cs)

    # Horizontal arm at top of plate
    arm = Part.makeBox(ARM_W, ARM_L, ARM_TH)
    arm.translate(Vector(0, ARM_TH, PLATE_H - ARM_TH))

    # 4× M4 panel mounting holes (⌀4.5) near far end of arm
    for xp in (5, ARM_W - 5):
        for yp in (ARM_L - 20, ARM_L - 8):
            hole = Part.makeCylinder(2.25, ARM_TH + 2)
            hole.translate(Vector(xp, ARM_TH + yp, PLATE_H - ARM_TH - 1))
            arm = arm.cut(hole)

    bracket = plate.fuse(arm)

    # Triangular gusset
    gusset_pts = [
        Vector(0,     ARM_TH, PLATE_H - ARM_TH),
        Vector(0,     ARM_TH + 25, PLATE_H - ARM_TH),
        Vector(0,     ARM_TH, PLATE_H - ARM_TH - 25),
        Vector(0,     ARM_TH, PLATE_H - ARM_TH),   # close polygon
    ]
    wire    = Part.makePolygon(gusset_pts)
    face    = Part.Face(wire)
    gusset  = face.extrude(Vector(ARM_W, 0, 0))
    bracket = bracket.fuse(gusset)

    return bracket


# ═══════════════════════════════════════════════════════════════════════════
#  BUILD DOCUMENT
# ═══════════════════════════════════════════════════════════════════════════

def add_part(shape, label, offset):
    shape.translate(Vector(*offset))
    obj = App.ActiveDocument.addObject("Part::Feature", label)
    obj.Shape = shape
    obj.Label = label
    return obj

doc_name = "CCTV_Enclosure"
try:
    App.closeDocument(doc_name)
except Exception:
    pass
doc = App.newDocument(doc_name)

print("Building CCTV enclosure parts…")

add_part(electronics_tray(), "1_Electronics_Tray", (0,          0, 0))
add_part(solar_bracket(),    "2_Solar_Bracket",    (BOX_W + 30, 0, 0))

doc.recompute()

try:
    Gui.ActiveDocument.ActiveView.viewIsometric()
    Gui.SendMsgToActiveView("ViewFit")
except Exception:
    pass

print("─" * 60)
print("Done. 2 parts created. Tree → right-click each → Export…")
print("  • STEP (.step)  — keep parametric / share with other CAD")
print("  • Mesh (.stl)   — straight to your 3D printer slicer")
print("─" * 60)
print("Assembly:")
print("  solar_bracket : screw vertical plate to wall with 2× M5.")
print("  Rest panel on top of arm, bolt through 4× M4 holes at end.")
print("─" * 60)
